Leaf-2026 DEFINITIONS IMPLICIT TAGS ::=
BEGIN

IMPORTS MidWrapper FROM Mid-2026;

BaseRecord ::= SEQUENCE {
    note UTF8String
}

LeafDocument ::= SEQUENCE {
    wrapper MidWrapper,
    local   BaseRecord
}

END
