-- PKIX-Flattened-2009
--
-- Flattened ASN.1 module derived from RFC 5912, "New ASN.1 Modules for
-- the Public Key Infrastructure Using X.509 (PKIX)", June 2010.
--
-- Sources:
--   PKIX-CommonTypes-2009   (RFC 5912 section 2)
--   PKIX1Explicit-2009      (RFC 5912 section 14)
--   PKIX1Implicit-2009      (RFC 5912 section 14)
--   AlgorithmIdentifier     (RFC 5912 section 3, AlgorithmInformation-2009)
--
-- Conversion:
--   This is a single self-contained module produced by merging the
--   source modules and the concrete form of AlgorithmIdentifier.
--   Information object constructs and their object sets are replaced by
--   concrete type definitions; parameterized types are expanded with the
--   actual arguments; open type fields use ANY, which retains the
--   complete original TLV and writes it back unchanged.  Fields whose
--   content is known to be OCTET STRING or another concrete type keep
--   that type.  See README.md and reconciliation.md in this directory
--   for the per-type rationale.
--
-- Copyright (c) 2010 IETF Trust and the persons identified as the
-- document authors.  All rights reserved.
--
-- This document is subject to BCP 78 and the IETF Trust's Legal
-- Provisions Relating to IETF Documents
-- (http://trustee.ietf.org/license-info) in effect on the date of
-- publication of this document.  Please review these documents
-- carefully, as they describe your rights and restrictions with respect
-- to this document.
--
-- Original text kept for comparison:
--   modules/pkix/asn1/reference/rfc5912/rfc5912.txt
-- Errata review:
--   modules/pkix/asn1/reference/rfc5912/errata.html

PKIX-Flattened-2009 DEFINITIONS IMPLICIT TAGS ::= BEGIN

-- ================================================================
-- Part 1: PKIX-CommonTypes-2009 (RFC 5912 section 2)
-- ================================================================
--
-- ATTRIBUTE, MATCHING-RULE and EXTENSION are information object
-- constructs.  They cannot be represented in the target syntax.  Their
-- uses are mapped as follows:
--   ATTRIBUTE ampersand id       -> OBJECT IDENTIFIER
--   ATTRIBUTE ampersand Type     -> ANY
--   EXTENSION ampersand id       -> OBJECT IDENTIFIER
--   EXTENSION ampersand ExtnType -> OCTET STRING
--   EXTENSION ampersand Critical -> BOOLEAN DEFAULT FALSE

-- Original: AttributeSet{ATTRIBUTE:AttrSet}
AttributeSet ::= SEQUENCE {
    type     OBJECT IDENTIFIER,
    values   SET SIZE (1..MAX) OF ANY
}

-- Original: SingleAttribute{ATTRIBUTE:AttrSet}
SingleAttribute ::= SEQUENCE {
    type     OBJECT IDENTIFIER,
    value    ANY
}

-- Original: Extension{EXTENSION:ExtensionSet}
Extension ::= SEQUENCE {
    extnID      OBJECT IDENTIFIER,
    critical    BOOLEAN DEFAULT FALSE,
    extnValue   OCTET STRING
}

-- Original: Extensions{EXTENSION:ExtensionSet}
Extensions ::= SEQUENCE SIZE (1..MAX) OF Extension

-- Original: SECURITY-CATEGORY was an information object alias.
-- The concrete structure below is the encoding of such an instance.
SECURITY-CATEGORY ::= SEQUENCE {
    type    [0] IMPLICIT OBJECT IDENTIFIER,
    value   [1] EXPLICIT ANY
}

-- Original: SecurityCategory{SECURITY-CATEGORY:Supported}
SecurityCategory ::= SECURITY-CATEGORY

-- ================================================================
-- Part 2: AlgorithmIdentifier (RFC 5912 section 3)
-- ================================================================
--
-- Original:
--   AlgorithmIdentifier{ALGORITHM-TYPE,
--                      ALGORITHM-TYPE:AlgorithmSet} ::= SEQUENCE {
--       algorithm   ALGORITHM-TYPE.ampersand id({AlgorithmSet}),
--       parameters  ALGORITHM-TYPE.ampersand Params(
--                       {AlgorithmSet}{@algorithm}) OPTIONAL
--   }
--
-- The open parameter field is represented as ANY: the full original TLV
-- is retained and written back unchanged.  See README.md section 7.
AlgorithmIdentifier ::= SEQUENCE {
    algorithm    OBJECT IDENTIFIER,
    parameters   ANY OPTIONAL
}

-- ================================================================
-- Part 3: PKIX1Explicit-2009 (RFC 5912 section 14)
-- ================================================================

-- Original: AttributeType ::= ATTRIBUTE.ampersand id
AttributeType ::= OBJECT IDENTIFIER

id-pkix OBJECT IDENTIFIER ::=
    { iso(1) identified-organization(3) dod(6) internet(1) security(5)
      mechanisms(5) pkix(7) }

-- PKIX arcs
id-pe OBJECT IDENTIFIER ::= { id-pkix 1 }
id-qt OBJECT IDENTIFIER ::= { id-pkix 2 }
id-kp OBJECT IDENTIFIER ::= { id-pkix 3 }
id-ad OBJECT IDENTIFIER ::= { id-pkix 48 }

-- policyQualifierIds for Internet policy qualifiers
id-qt-cps      OBJECT IDENTIFIER ::= { id-qt 1 }
id-qt-unotice  OBJECT IDENTIFIER ::= { id-qt 2 }

-- access descriptor definitions
id-ad-ocsp         OBJECT IDENTIFIER ::= { id-ad 1 }
id-ad-caIssuers    OBJECT IDENTIFIER ::= { id-ad 2 }
id-ad-timeStamping OBJECT IDENTIFIER ::= { id-ad 3 }
id-ad-caRepository OBJECT IDENTIFIER ::= { id-ad 5 }

-- Arc for standard naming attributes
id-at OBJECT IDENTIFIER ::= { joint-iso-ccitt(2) ds(5) 4 }

-- Naming attribute OIDs.  The corresponding at-* ATTRIBUTE information
-- objects are intentionally not present; see reconciliation.md.
id-at-name                AttributeType ::= { id-at 41 }
id-at-surname             AttributeType ::= { id-at 4 }
id-at-givenName           AttributeType ::= { id-at 42 }
id-at-initials            AttributeType ::= { id-at 43 }
id-at-generationQualifier AttributeType ::= { id-at 44 }
id-at-commonName          AttributeType ::= { id-at 3 }
id-at-localityName        AttributeType ::= { id-at 7 }
id-at-stateOrProvinceName AttributeType ::= { id-at 8 }
id-at-organizationName    AttributeType ::= { id-at 10 }
id-at-organizationalUnitName AttributeType ::= { id-at 11 }
id-at-title               AttributeType ::= { id-at 12 }
id-at-dnQualifier         AttributeType ::= { id-at 46 }
id-at-countryName         AttributeType ::= { id-at 6 }
id-at-serialNumber        AttributeType ::= { id-at 5 }
id-at-pseudonym           AttributeType ::= { id-at 65 }
id-domainComponent        AttributeType ::=
    { itu-t(0) data(9) pss(2342) ucl(19200300) pilot(100)
      pilotAttributeType(1) 25 }

-- Legacy attributes
pkcs-9 OBJECT IDENTIFIER ::=
    { iso(1) member-body(2) us(840) rsadsi(113549) pkcs(1) 9 }
id-emailAddress AttributeType ::= { pkcs-9 1 }

-- Directory string type.
-- Original: DirectoryString{INTEGER:maxSize}, a parameterized CHOICE.
-- The base type uses MAX; each instance below is expanded with the
-- concrete upper bound that the instance used.
DirectoryString ::= CHOICE {
    teletexString    TeletexString    (SIZE (1..MAX)),
    printableString  PrintableString  (SIZE (1..MAX)),
    bmpString        BMPString        (SIZE (1..MAX)),
    universalString  UniversalString  (SIZE (1..MAX)),
    uTF8String       UTF8String       (SIZE (1..MAX))
}

-- Original: X520name ::= DirectoryString {ub-name}, ub-name = 32768
X520name ::= CHOICE {
    teletexString    TeletexString    (SIZE (1..32768)),
    printableString  PrintableString  (SIZE (1..32768)),
    bmpString        BMPString        (SIZE (1..32768)),
    universalString  UniversalString  (SIZE (1..32768)),
    uTF8String       UTF8String       (SIZE (1..32768))
}

-- Original: X520CommonName ::= DirectoryString {ub-common-name}
X520CommonName ::= CHOICE {
    teletexString    TeletexString    (SIZE (1..64)),
    printableString  PrintableString  (SIZE (1..64)),
    bmpString        BMPString        (SIZE (1..64)),
    universalString  UniversalString  (SIZE (1..64)),
    uTF8String       UTF8String       (SIZE (1..64))
}

-- Original: X520LocalityName ::= DirectoryString {ub-locality-name}
X520LocalityName ::= CHOICE {
    teletexString    TeletexString    (SIZE (1..128)),
    printableString  PrintableString  (SIZE (1..128)),
    bmpString        BMPString        (SIZE (1..128)),
    universalString  UniversalString  (SIZE (1..128)),
    uTF8String       UTF8String       (SIZE (1..128))
}

-- Original: X520StateOrProvinceName ::= DirectoryString {ub-state-name}
X520StateOrProvinceName ::= CHOICE {
    teletexString    TeletexString    (SIZE (1..128)),
    printableString  PrintableString  (SIZE (1..128)),
    bmpString        BMPString        (SIZE (1..128)),
    universalString  UniversalString  (SIZE (1..128)),
    uTF8String       UTF8String       (SIZE (1..128))
}

-- Original: X520OrganizationName ::= DirectoryString {ub-organization-name}
X520OrganizationName ::= CHOICE {
    teletexString    TeletexString    (SIZE (1..64)),
    printableString  PrintableString  (SIZE (1..64)),
    bmpString        BMPString        (SIZE (1..64)),
    universalString  UniversalString  (SIZE (1..64)),
    uTF8String       UTF8String       (SIZE (1..64))
}

-- Original: X520OrganizationalUnitName ::=
--               DirectoryString {ub-organizational-unit-name}
X520OrganizationalUnitName ::= CHOICE {
    teletexString    TeletexString    (SIZE (1..64)),
    printableString  PrintableString  (SIZE (1..64)),
    bmpString        BMPString        (SIZE (1..64)),
    universalString  UniversalString  (SIZE (1..64)),
    uTF8String       UTF8String       (SIZE (1..64))
}

-- Naming data types
Name ::= CHOICE {
    rdnSequence  RDNSequence
}

RDNSequence ::= SEQUENCE OF RelativeDistinguishedName

DistinguishedName ::= RDNSequence

-- Original:
--   RelativeDistinguishedName ::=
--       SET SIZE (1..MAX) OF SingleAttribute {{SupportedAttributes}}
RelativeDistinguishedName ::= SET SIZE (1..MAX) OF SingleAttribute

-- Certificate and CRL structures
-- Original: Certificate ::= SIGNED{TBSCertificate}
Certificate ::= SIGNED-TBSCertificate

TBSCertificate ::= SEQUENCE {
    version              [0] EXPLICIT Version DEFAULT v1,
    serialNumber         CertificateSerialNumber,
    signature            AlgorithmIdentifier,
    issuer               Name,
    validity             Validity,
    subject              Name,
    subjectPublicKeyInfo SubjectPublicKeyInfo,
    ...,
    issuerUniqueID       [1] IMPLICIT UniqueIdentifier OPTIONAL,
    subjectUniqueID      [2] IMPLICIT UniqueIdentifier OPTIONAL,
    extensions           [3] EXPLICIT Extensions OPTIONAL
}

Version ::= INTEGER { v1(0), v2(1), v3(2) }

CertificateSerialNumber ::= INTEGER

Validity ::= SEQUENCE {
    notBefore  Time,
    notAfter   Time
}

Time ::= CHOICE {
    utcTime      UTCTime,
    generalTime  GeneralizedTime
}

UniqueIdentifier ::= BIT STRING

SubjectPublicKeyInfo ::= SEQUENCE {
    algorithm         AlgorithmIdentifier,
    subjectPublicKey  BIT STRING
}

-- Original: CertificateList ::= SIGNED{TBSCertList}
CertificateList ::= SIGNED-TBSCertList

TBSCertList ::= SEQUENCE {
    version              Version OPTIONAL,
    signature            AlgorithmIdentifier,
    issuer               Name,
    thisUpdate           Time,
    nextUpdate           Time OPTIONAL,
    revokedCertificates  SEQUENCE SIZE (1..MAX) OF SEQUENCE {
        userCertificate    CertificateSerialNumber,
        revocationDate     Time,
        ...,
        crlEntryExtensions Extensions OPTIONAL
    } OPTIONAL,
    ...,
    crlExtensions        [0] EXPLICIT Extensions OPTIONAL
}

-- Original: SIGNED{ToBeSigned}, a parameterized SEQUENCE.
-- Expanded to one concrete type per actual argument.
SIGNED-TBSCertificate ::= SEQUENCE {
    toBeSigned            TBSCertificate,
    algorithmIdentifier   AlgorithmIdentifier,
    signature             BIT STRING
}

SIGNED-TBSCertList ::= SEQUENCE {
    toBeSigned            TBSCertList,
    algorithmIdentifier   AlgorithmIdentifier,
    signature             BIT STRING
}

-- Upper bounds
ub-state-name                INTEGER ::= 128
ub-organization-name         INTEGER ::= 64
ub-organizational-unit-name  INTEGER ::= 64
ub-title                     INTEGER ::= 64
ub-serial-number             INTEGER ::= 64
ub-pseudonym                 INTEGER ::= 128
ub-emailaddress-length       INTEGER ::= 255
ub-locality-name             INTEGER ::= 128
ub-common-name               INTEGER ::= 64
ub-name                      INTEGER ::= 32768

-- ================================================================
-- Part 4: PKIX1Implicit-2009 (RFC 5912 section 14)
-- ================================================================

-- Shared arc for standard certificate and CRL extensions
id-ce OBJECT IDENTIFIER ::= { joint-iso-ccitt(2) ds(5) 29 }

-- authority key identifier OID and syntax
id-ce-authorityKeyIdentifier OBJECT IDENTIFIER ::= { id-ce 35 }

AuthorityKeyIdentifier ::= SEQUENCE {
    keyIdentifier             [0] KeyIdentifier OPTIONAL,
    authorityCertIssuer       [1] GeneralNames OPTIONAL,
    authorityCertSerialNumber [2] CertificateSerialNumber OPTIONAL
}

KeyIdentifier ::= OCTET STRING

-- subject key identifier OID and syntax
id-ce-subjectKeyIdentifier OBJECT IDENTIFIER ::= { id-ce 14 }

-- key usage extension OID and syntax
id-ce-keyUsage OBJECT IDENTIFIER ::= { id-ce 15 }

KeyUsage ::= BIT STRING {
    digitalSignature  (0),
    nonRepudiation    (1),
    keyEncipherment   (2),
    dataEncipherment  (3),
    keyAgreement      (4),
    keyCertSign       (5),
    cRLSign           (6),
    encipherOnly      (7),
    decipherOnly      (8)
}

-- private key usage period extension OID and syntax
id-ce-privateKeyUsagePeriod OBJECT IDENTIFIER ::= { id-ce 16 }

PrivateKeyUsagePeriod ::= SEQUENCE {
    notBefore  [0] GeneralizedTime OPTIONAL,
    notAfter   [1] GeneralizedTime OPTIONAL
}

-- certificate policies extension OID and syntax
id-ce-certificatePolicies OBJECT IDENTIFIER ::= { id-ce 32 }

CertificatePolicies ::= SEQUENCE SIZE (1..MAX) OF PolicyInformation

PolicyInformation ::= SEQUENCE {
    policyIdentifier  CertPolicyId,
    policyQualifiers  SEQUENCE SIZE (1..MAX) OF PolicyQualifierInfo OPTIONAL
}

CertPolicyId ::= OBJECT IDENTIFIER

-- Original: CERT-POLICY-QUALIFIER was an information object alias.
-- Replaced by the concrete field structure used by PolicyQualifierInfo.
CERT-POLICY-QUALIFIER ::= SEQUENCE {
    policyQualifierId  OBJECT IDENTIFIER,
    qualifier          ANY
}

PolicyQualifierInfo ::= CERT-POLICY-QUALIFIER

CPSuri ::= IA5String

UserNotice ::= SEQUENCE {
    noticeRef     NoticeReference OPTIONAL,
    explicitText  DisplayText OPTIONAL
}

NoticeReference ::= SEQUENCE {
    organization   DisplayText,
    noticeNumbers  SEQUENCE OF INTEGER
}

DisplayText ::= CHOICE {
    ia5String      IA5String      (SIZE (1..200)),
    visibleString  VisibleString  (SIZE (1..200)),
    bmpString      BMPString      (SIZE (1..200)),
    utf8String     UTF8String     (SIZE (1..200))
}

-- policy mapping extension OID and syntax
id-ce-policyMappings OBJECT IDENTIFIER ::= { id-ce 33 }

PolicyMappings ::= SEQUENCE SIZE (1..MAX) OF SEQUENCE {
    issuerDomainPolicy   CertPolicyId,
    subjectDomainPolicy  CertPolicyId
}

-- subject alternative name extension OID and syntax
id-ce-subjectAltName OBJECT IDENTIFIER ::= { id-ce 17 }

GeneralNames ::= SEQUENCE SIZE (1..MAX) OF GeneralName

-- Original otherName alternative:
--   otherName [0] OTHER-NAME  (information object instance form)
-- Original x400Address alternative:
--   x400Address [3] ORAddress
-- ORAddress belongs to PKIX-X400Address-2009 and is not carried over.
-- This alternative is NOT an open type: its content is ORAddress, not
-- an arbitrary type.  It is represented as OCTET STRING and cannot be
-- read structurally in phase 1.  See README.md section 7.
GeneralName ::= CHOICE {
    otherName                [0] OTHER-NAME,
    rfc822Name               [1] IA5String,
    dNSName                  [2] IA5String,
    x400Address              [3] OCTET STRING,
    directoryName            [4] Name,
    ediPartyName             [5] EDIPartyName,
    uniformResourceIdentifier [6] IA5String,
    iPAddress                [7] OCTET STRING,
    registeredID             [8] OBJECT IDENTIFIER
}

-- Original: OTHER-NAME was an information object alias.
-- Concrete encoding of such an instance.
OTHER-NAME ::= SEQUENCE {
    type-id  OBJECT IDENTIFIER,
    value    [0] EXPLICIT ANY
}

EDIPartyName ::= SEQUENCE {
    nameAssigner  [0] DirectoryString OPTIONAL,
    partyName     [1] DirectoryString
}

-- issuer alternative name extension OID and syntax
id-ce-issuerAltName OBJECT IDENTIFIER ::= { id-ce 18 }

-- subject directory attributes extension OID and syntax
id-ce-subjectDirectoryAttributes OBJECT IDENTIFIER ::= { id-ce 9 }

SubjectDirectoryAttributes ::= SEQUENCE SIZE (1..MAX) OF AttributeSet

-- basic constraints extension OID and syntax
id-ce-basicConstraints OBJECT IDENTIFIER ::= { id-ce 19 }

BasicConstraints ::= SEQUENCE {
    cA                 BOOLEAN DEFAULT FALSE,
    pathLenConstraint  INTEGER (0..MAX) OPTIONAL
}

-- name constraints extension OID and syntax
id-ce-nameConstraints OBJECT IDENTIFIER ::= { id-ce 30 }

NameConstraints ::= SEQUENCE {
    permittedSubtrees  [0] GeneralSubtrees OPTIONAL,
    excludedSubtrees   [1] GeneralSubtrees OPTIONAL
}

GeneralSubtrees ::= SEQUENCE SIZE (1..MAX) OF GeneralSubtree

GeneralSubtree ::= SEQUENCE {
    base      GeneralName,
    minimum   [0] BaseDistance DEFAULT 0,
    maximum   [1] BaseDistance OPTIONAL
}

BaseDistance ::= INTEGER (0..MAX)

-- policy constraints extension OID and syntax
id-ce-policyConstraints OBJECT IDENTIFIER ::= { id-ce 36 }

PolicyConstraints ::= SEQUENCE {
    requireExplicitPolicy  [0] SkipCerts OPTIONAL,
    inhibitPolicyMapping   [1] SkipCerts OPTIONAL
}

SkipCerts ::= INTEGER (0..MAX)

-- CRL distribution points extension OID and syntax
id-ce-cRLDistributionPoints OBJECT IDENTIFIER ::= { id-ce 31 }

CRLDistributionPoints ::= SEQUENCE SIZE (1..MAX) OF DistributionPoint

DistributionPoint ::= SEQUENCE {
    distributionPoint  [0] DistributionPointName OPTIONAL,
    reasons            [1] ReasonFlags OPTIONAL,
    cRLIssuer          [2] GeneralNames OPTIONAL
}

DistributionPointName ::= CHOICE {
    fullName                 [0] GeneralNames,
    nameRelativeToCRLIssuer  [1] RelativeDistinguishedName
}

ReasonFlags ::= BIT STRING {
    unused                (0),
    keyCompromise         (1),
    cACompromise          (2),
    affiliationChanged    (3),
    superseded            (4),
    cessationOfOperation  (5),
    certificateHold       (6),
    privilegeWithdrawn    (7),
    aACompromise          (8)
}

-- extended key usage extension OID and syntax
id-ce-extKeyUsage OBJECT IDENTIFIER ::= { id-ce 37 }

ExtKeyUsageSyntax ::= SEQUENCE SIZE (1..MAX) OF KeyPurposeId

KeyPurposeId ::= OBJECT IDENTIFIER

-- permit unspecified key uses
anyExtendedKeyUsage OBJECT IDENTIFIER ::= { id-ce-extKeyUsage 0 }

-- extended key purpose OIDs
id-kp-serverAuth      OBJECT IDENTIFIER ::= { id-kp 1 }
id-kp-clientAuth      OBJECT IDENTIFIER ::= { id-kp 2 }
id-kp-codeSigning     OBJECT IDENTIFIER ::= { id-kp 3 }
id-kp-emailProtection OBJECT IDENTIFIER ::= { id-kp 4 }
id-kp-timeStamping    OBJECT IDENTIFIER ::= { id-kp 8 }
id-kp-OCSPSigning     OBJECT IDENTIFIER ::= { id-kp 9 }

-- inhibit-policy extension OID and syntax
id-ce-inhibitAnyPolicy OBJECT IDENTIFIER ::= { id-ce 54 }

-- freshest (delta) CRL extension OID and syntax
id-ce-freshestCRL OBJECT IDENTIFIER ::= { id-ce 46 }

-- authority info access
id-pe-authorityInfoAccess OBJECT IDENTIFIER ::= { id-pe 1 }

AuthorityInfoAccessSyntax ::= SEQUENCE SIZE (1..MAX) OF AccessDescription

AccessDescription ::= SEQUENCE {
    accessMethod    OBJECT IDENTIFIER,
    accessLocation  GeneralName
}

-- subject info access
id-pe-subjectInfoAccess OBJECT IDENTIFIER ::= { id-pe 11 }

SubjectInfoAccessSyntax ::= SEQUENCE SIZE (1..MAX) OF AccessDescription

-- CRL number extension OID and syntax
id-ce-cRLNumber OBJECT IDENTIFIER ::= { id-ce 20 }

CRLNumber ::= INTEGER (0..MAX)

-- issuing distribution point extension OID and syntax
id-ce-issuingDistributionPoint OBJECT IDENTIFIER ::= { id-ce 28 }

IssuingDistributionPoint ::= SEQUENCE {
    distributionPoint          [0] DistributionPointName OPTIONAL,
    onlyContainsUserCerts      [1] BOOLEAN DEFAULT FALSE,
    onlyContainsCACerts        [2] BOOLEAN DEFAULT FALSE,
    onlySomeReasons            [3] ReasonFlags OPTIONAL,
    indirectCRL                [4] BOOLEAN DEFAULT FALSE,
    onlyContainsAttributeCerts [5] BOOLEAN DEFAULT FALSE
}

id-ce-deltaCRLIndicator OBJECT IDENTIFIER ::= { id-ce 27 }

-- CRL reasons extension OID and syntax
id-ce-cRLReasons OBJECT IDENTIFIER ::= { id-ce 21 }

CRLReason ::= ENUMERATED {
    unspecified          (0),
    keyCompromise        (1),
    cACompromise         (2),
    affiliationChanged   (3),
    superseded           (4),
    cessationOfOperation (5),
    certificateHold      (6),
    removeFromCRL        (8),
    privilegeWithdrawn   (9),
    aACompromise         (10)
}

-- certificate issuer CRL entry extension OID and syntax
id-ce-certificateIssuer OBJECT IDENTIFIER ::= { id-ce 29 }

-- hold instruction extension OID and syntax
id-ce-holdInstructionCode OBJECT IDENTIFIER ::= { id-ce 23 }

-- ANSI x9 holdinstructions
holdInstruction OBJECT IDENTIFIER ::=
    { joint-iso-itu-t(2) member-body(2) us(840) x9cm(10040) 2 }

id-holdinstruction-none OBJECT IDENTIFIER ::= { holdInstruction 1 }

id-holdinstruction-callissuer OBJECT IDENTIFIER ::= { holdInstruction 2 }

id-holdinstruction-reject OBJECT IDENTIFIER ::= { holdInstruction 3 }

-- invalidity date CRL entry extension OID and syntax
id-ce-invalidityDate OBJECT IDENTIFIER ::= { id-ce 24 }

-- Upper bounds
ubMax INTEGER ::= 32768

END
