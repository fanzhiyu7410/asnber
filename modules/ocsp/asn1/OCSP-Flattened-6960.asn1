-- OCSP-Flattened-6960
--
-- 自包含展平模块，来源是 RFC 6960 附录的 1988 模块。
-- 附录原文是 EXPLICIT TAGS。这里写成 IMPLICIT TAGS，是因为每个带标签的
-- 字段都已经写明 EXPLICIT 或 IMPLICIT：线上编码与附录相同，而未写标签的
-- SEQUENCE 仍使用自己的通用标签。CertStatus 的三支保持 IMPLICIT。
-- 差别见同目录 reconciliation.md。本文件只描述结构，不验签、不判断证书状态。
OCSP-Flattened-6960
    DEFINITIONS IMPLICIT TAGS ::=
BEGIN

-- 占位：保留完整 TLV，不展开 PKIX 的 Certificate / Name / GeneralName。
Certificate ::= ANY
Name ::= ANY
GeneralName ::= ANY

CertificateSerialNumber ::= INTEGER

AlgorithmIdentifier ::= SEQUENCE {
    algorithm    OBJECT IDENTIFIER,
    parameters   ANY OPTIONAL
}

Extension ::= SEQUENCE {
    extnID      OBJECT IDENTIFIER,
    critical    BOOLEAN DEFAULT FALSE,
    extnValue   OCTET STRING
}

Extensions ::= SEQUENCE SIZE (1..MAX) OF Extension

-- 勘误 3259：用 PKIX 的 ENUMERATED，不用 RFC 6960 正文里的 INTEGER。
CRLReason ::= ENUMERATED {
    unspecified          (0),
    keyCompromise        (1),
    cACompromise         (2),
    affiliationChanged   (3),
    superseded           (4),
    cessationOfOperation (5),
    certificateHold      (6),
    removeFromCRL        (8),
    privilegeWithdrawn   (9),
    aACompromise         (10)
}

Version ::= INTEGER { v1(0) }

CertID ::= SEQUENCE {
    hashAlgorithm   AlgorithmIdentifier,
    issuerNameHash  OCTET STRING,
    issuerKeyHash   OCTET STRING,
    serialNumber    CertificateSerialNumber
}

Request ::= SEQUENCE {
    reqCert                  CertID,
    singleRequestExtensions  [0] EXPLICIT Extensions OPTIONAL
}

TBSRequest ::= SEQUENCE {
    version            [0] EXPLICIT Version DEFAULT v1,
    requestorName      [1] EXPLICIT GeneralName OPTIONAL,
    requestList            SEQUENCE OF Request,
    requestExtensions  [2] EXPLICIT Extensions OPTIONAL
}

Signature ::= SEQUENCE {
    signatureAlgorithm  AlgorithmIdentifier,
    signature           BIT STRING,
    certs               [0] EXPLICIT SEQUENCE OF Certificate OPTIONAL
}

OCSPRequest ::= SEQUENCE {
    tbsRequest          TBSRequest,
    optionalSignature   [0] EXPLICIT Signature OPTIONAL
}

OCSPResponseStatus ::= ENUMERATED {
    successful        (0),
    malformedRequest  (1),
    internalError     (2),
    tryLater          (3),
    sigRequired       (5),
    unauthorized      (6)
}

ResponseBytes ::= SEQUENCE {
    responseType  OBJECT IDENTIFIER,
    response      OCTET STRING
}

OCSPResponse ::= SEQUENCE {
    responseStatus  OCSPResponseStatus,
    responseBytes   [0] EXPLICIT ResponseBytes OPTIONAL
}

KeyHash ::= OCTET STRING

ResponderID ::= CHOICE {
    byName  [1] EXPLICIT Name,
    byKey   [2] EXPLICIT KeyHash
}

RevokedInfo ::= SEQUENCE {
    revocationTime    GeneralizedTime,
    revocationReason  [0] EXPLICIT CRLReason OPTIONAL
}

CertStatus ::= CHOICE {
    good     [0] IMPLICIT NULL,
    revoked  [1] IMPLICIT RevokedInfo,
    unknown  [2] IMPLICIT NULL
}

SingleResponse ::= SEQUENCE {
    certID             CertID,
    certStatus         CertStatus,
    thisUpdate         GeneralizedTime,
    nextUpdate         [0] EXPLICIT GeneralizedTime OPTIONAL,
    singleExtensions   [1] EXPLICIT Extensions OPTIONAL
}

ResponseData ::= SEQUENCE {
    version             [0] EXPLICIT Version DEFAULT v1,
    responderID             ResponderID,
    producedAt              GeneralizedTime,
    responses               SEQUENCE OF SingleResponse,
    responseExtensions  [1] EXPLICIT Extensions OPTIONAL
}

BasicOCSPResponse ::= SEQUENCE {
    tbsResponseData     ResponseData,
    signatureAlgorithm  AlgorithmIdentifier,
    signature           BIT STRING,
    certs               [0] EXPLICIT SEQUENCE OF Certificate OPTIONAL
}

id-pkix OBJECT IDENTIFIER ::= {
    iso(1) identified-organization(3) dod(6) internet(1) security(5)
    mechanisms(5) pkix(7)
}
id-ad OBJECT IDENTIFIER ::= { id-pkix 48 }
id-ad-ocsp OBJECT IDENTIFIER ::= { id-ad 1 }
id-kp OBJECT IDENTIFIER ::= { id-pkix 3 }
id-kp-OCSPSigning OBJECT IDENTIFIER ::= { id-kp 9 }

id-pkix-ocsp OBJECT IDENTIFIER ::= { id-ad-ocsp }
id-pkix-ocsp-basic OBJECT IDENTIFIER ::= { id-pkix-ocsp 1 }
id-pkix-ocsp-nonce OBJECT IDENTIFIER ::= { id-pkix-ocsp 2 }
id-pkix-ocsp-crl OBJECT IDENTIFIER ::= { id-pkix-ocsp 3 }
id-pkix-ocsp-response OBJECT IDENTIFIER ::= { id-pkix-ocsp 4 }
id-pkix-ocsp-nocheck OBJECT IDENTIFIER ::= { id-pkix-ocsp 5 }
id-pkix-ocsp-archive-cutoff OBJECT IDENTIFIER ::= { id-pkix-ocsp 6 }
id-pkix-ocsp-service-locator OBJECT IDENTIFIER ::= { id-pkix-ocsp 7 }
id-pkix-ocsp-pref-sig-algs OBJECT IDENTIFIER ::= { id-pkix-ocsp 8 }
id-pkix-ocsp-extended-revoke OBJECT IDENTIFIER ::= { id-pkix-ocsp 9 }

END
